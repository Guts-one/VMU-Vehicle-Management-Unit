# HEV_powersplit_adapted_swllr

## SwLLR01: Standstill Mode to EV Mode (Functional)
When the active software mode is the standstill mode and speed > SPEED_STOP && speed <= SPEED_EV_MAX && SOC >= SOC_EV_IN, the software shall transition to EV mode.

## SwLLR02: Standstill Mode to Start Mode (Functional)
When the active software mode is the standstill mode and speed > SPEED_STOP && (speed > SPEED_EV_MAX || SOC < SOC_EV_IN), the software shall transition to Start mode.

## SwLLR03: EV Mode to Regenerative-Braking Mode (Functional)
When the active software mode is EV mode and speed > SPEED_REGEN && P_dem <= PDEM_REGEN, the software shall transition to the regenerative-braking mode.

## SwLLR04: EV Mode to Start Mode (Functional)
When the active software mode is EV mode and (speed > SPEED_EV_MAX || P_dem >= PDEM_HYB_IN || SOC < SOC_EV_OUT), the software shall transition to Start mode.

## SwLLR05: EV Mode to Standstill Mode (Functional)
When the active software mode is EV mode and speed <= SPEED_STOP && P_dem <= PDEM_STOP_HIGH && P_dem >= PDEM_STOP_LOW, the software shall transition to the standstill mode.

## SwLLR06: Regenerative-Braking Mode to Start Mode (Functional)
When the active software mode is the regenerative-braking mode and (((speed > SPEED_EV_MAX) && (P_dem >= PDEM_STOP_LOW)) || SOC < SOC_EV_OUT), the software shall transition to Start mode.

## SwLLR07: Regenerative-Braking Mode to Standstill Mode (Functional)
When the active software mode is the regenerative-braking mode and speed <= SPEED_STOP && P_dem <= PDEM_STOP_HIGH && P_dem >= PDEM_STOP_LOW, the software shall transition to the standstill mode.

## SwLLR08: Regenerative-Braking Mode to EV Mode (Functional)
When the active software mode is the regenerative-braking mode and P_dem >= PDEM_STOP_LOW && speed > SPEED_STOP && speed <= SPEED_EV_MAX && SOC >= SOC_EV_OUT, the software shall transition to EV mode.

## SwLLR09: Start Mode to Regenerative-Braking Mode (Functional)
When the active software mode is Start mode and wEng > ENG_ON && speed > SPEED_REGEN && P_dem <= PDEM_REGEN, the software shall transition to the regenerative-braking mode.

## SwLLR10: ICE Mode to Regenerative-Braking Mode (Functional)
When the active software mode is ICE mode and wEng > ENG_ON && speed > SPEED_REGEN && P_dem <= PDEM_REGEN, the software shall transition to the regenerative-braking mode.

## SwLLR11: Hybrid Mode to Regenerative-Braking Mode (Functional)
When the active software mode is Hybrid mode and wEng > ENG_ON && speed > SPEED_REGEN && P_dem <= PDEM_REGEN, the software shall transition to the regenerative-braking mode.

## SwLLR12: Start Mode to EV Mode (Functional)
When the active software mode is Start mode and wEng > ENG_ON && P_dem <= PDEM_HYB_OUT && P_dem >= PDEM_STOP_LOW && speed > SPEED_STOP && speed <= SPEED_EV_MAX && SOC >= SOC_EV_IN, the software shall transition to EV mode.

## SwLLR13: ICE Mode to EV Mode (Functional)
When the active software mode is ICE mode and wEng > ENG_ON && P_dem <= PDEM_HYB_OUT && P_dem >= PDEM_STOP_LOW && speed > SPEED_STOP && speed <= SPEED_EV_MAX && SOC >= SOC_EV_IN, the software shall transition to EV mode.

## SwLLR14: Hybrid Mode to EV Mode (Functional)
When the active software mode is Hybrid mode and wEng > ENG_ON && P_dem <= PDEM_HYB_OUT && P_dem >= PDEM_STOP_LOW && speed > SPEED_STOP && speed <= SPEED_EV_MAX && SOC >= SOC_EV_IN, the software shall transition to EV mode.

## SwLLR15: Start Mode to Standstill Mode (Functional)
When the active software mode is Start mode and speed <= SPEED_STOP && P_dem <= PDEM_STOP_HIGH && P_dem >= PDEM_STOP_LOW, the software shall transition to the standstill mode.

## SwLLR16: ICE Mode to Standstill Mode (Functional)
When the active software mode is ICE mode and speed <= SPEED_STOP && P_dem <= PDEM_STOP_HIGH && P_dem >= PDEM_STOP_LOW, the software shall transition to the standstill mode.

## SwLLR17: Hybrid Mode to Standstill Mode (Functional)
When the active software mode is Hybrid mode and speed <= SPEED_STOP && P_dem <= PDEM_STOP_HIGH && P_dem >= PDEM_STOP_LOW, the software shall transition to the standstill mode.

## SwLLR18: Start Mode to Hybrid Mode (Functional)
When the active software mode is Start mode and wEng > ENG_ON && SOC >= SOC_MID && (speed > SPEED_EV_MAX || P_dem >= PDEM_HYB_MID), the software shall transition to Hybrid mode.

## SwLLR19: Start Mode to ICE Mode (Functional)
When the active software mode is Start mode and wEng > ENG_ON && (SOC < SOC_MID || (speed <= SPEED_EV_MAX && P_dem < PDEM_HYB_MID)), the software shall transition to ICE mode.

## SwLLR20: ICE Mode to Start Mode (Functional)
When the active software mode is ICE mode and wEng <= ENG_OFF, the software shall transition to Start mode.

## SwLLR21: ICE Mode to Hybrid Mode (Functional)
When the active software mode is ICE mode and P_dem >= PDEM_HYB_MID && SOC >= SOC_MID, the software shall transition to Hybrid mode.

## SwLLR22: Hybrid Mode to Start Mode (Functional)
When the active software mode is Hybrid mode and wEng <= ENG_OFF, the software shall transition to Start mode.

## SwLLR23: Hybrid Mode to ICE Mode (Functional)
When the active software mode is Hybrid mode and (P_dem <= PDEM_HYB_LOW || SOC < SOC_LOW), the software shall transition to ICE mode.
